FME workspace ConnectingNode.fmw

Parameters:
- SourceDataset_GML = C:\Temp\Highways_Data\Paths\Bedford_ConnectingNode.gml.gz   # Source Geography Markup Language (GML) File(s)
- DestDataset_GEOPACKAGE =   # Destination GeoPackage File

Readers:
- GML_1: GML from $(SourceDataset_GML)

Writers:
- GEOPACKAGE_1: GEOPACKAGE to $(DestDataset_GEOPACKAGE)

Note: Set input to local GML files
Note: Rename ID to TOID and other attributes to make easier to read
Note: Creates node geometry for connecting roadlinks and pathlinks
ConnectingNode (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, reasonForChange xml_buffer, reasonForChange.codeSpace xml_buffer, geometry xml_geometry, roadLink.nilReason xml_buffer, roadLink.gml_remoteSchema xml_buffer, roadLink.xlink_href xml_buffer, roadLink.owns xml_boolean, roadLink.xsi_nil xml_boolean
    -> AttributeRenamer
Note: Change output to prefered format
ConnectingNode (writer GEOPACKAGE_1)
    attributes: TOID text(20), beginLifespanVersion datetime, reasonForChange text(20), roadLink text(20)

Bookmark: Create connectingNode
AttributeRenamer
    ATTR_TABLE:
      RENAME_SET_DEFAULT gml_id > TOID
      RENAME_SET_DEFAULT roadLink.xlink_href > roadLink
    -> DateFormatter
DateFormatter
    FMT = FME Date (%Y%m%d)
    DATE_ATTR = beginLifespanVersion
    SRCFMT = Unknown - Automatic Detection
    INVALID_DATE_VALUE = FME_NULL_VALUE
    -> StringReplacer
Note: Remove unwanted #
StringReplacer
    REGEXP = NO
    FIND_TEXT = #
    SRC_ATTRS = roadLink
    NO_MATCH = _FME_NO_OP_
    CASE = NO
    -> ConnectingNode (writer GEOPACKAGE_1)
