FME workspace highwayDedication.fmw

Parameters:
- SourceDataset_GML = C:\Data\OSMasterMap\Highways\FME\Update\Highways_Rrami_Dedication_FULL_001.gml.gz   # Source Geography Markup Language (GML) File(s)
- DestDataset_GEOPACKAGE = $(FME_MF_DIR)test.gpkg   # GeoPackage File

Readers:
- GML_1: GML from $(SourceDataset_GML) in EPSG:27700

Writers:
- GEOPACKAGE_1: GEOPACKAGE to $(DestDataset_GEOPACKAGE)

Note: Change location of input GML files
HighwayDedication (reader GML_1)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer, networkRef{}.LinkReference.applicableDirection.xsi_nil xml_boolean, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean, networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean,
      networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer, networkRef{}.PointReference.offset.xsi_nil xml_boolean, networkRef{}.PointReference.atPositionGeometry xml_geometry, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64,
      networkRef{}.SimpleLinearReference.offset.nilReason xml_buffer, networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer, networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NetworkReferenceLocation.locationLine xml_geometry,
      networkRef{}.NetworkReferenceLocation.locationArea xml_geometry, networkRef{}.NodeReference.element.owns xml_boolean, networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, reasonForChange xml_buffer, reasonForChange.codeSpace xml_buffer, dedication xml_buffer,
      dedication.codeSpace xml_buffer, timeInterval{}.TemporalPropertyType.namedDate{} xml_buffer, timeInterval{}.TemporalPropertyType.namedDate{}.codeSpace xml_buffer, timeInterval{}.TemporalPropertyType.dateRange{}.DateRangeType.startDate xml_date, timeInterval{}.TemporalPropertyType.dateRange{}.DateRangeType.endDate xml_date, timeInterval{}.TemporalPropertyType.dateRange{}.DateRangeType.startMonthDay xml_buffer, timeInterval{}.TemporalPropertyType.dateRange{}.DateRangeType.endMonthDay xml_buffer, timeInterval{}.TemporalPropertyType.dayPeriod{}.DayPropertyType.namedDay{} xml_buffer, timeInterval{}.TemporalPropertyType.dayPeriod{}.DayPropertyType.namedDay{}.codeSpace xml_buffer, timeInterval{}.TemporalPropertyType.dayPeriod{}.DayPropertyType.namedPeriod{} xml_buffer, timeInterval{}.TemporalPropertyType.dayPeriod{}.DayPropertyType.namedPeriod{}.codeSpace xml_buffer, timeInterval{}.TemporalPropertyType.dayPeriod{}.DayPropertyType.timePeriod{}.TimePropertyType.namedTime{} xml_buffer, timeInterval{}.TemporalPropertyType.dayPeriod{}.DayPropertyType.timePeriod{}.TimePropertyType.namedTime{}.codeSpace xml_buffer, timeInterval{}.TemporalPropertyType.dayPeriod{}.DayPropertyType.timePeriod{}.TimePropertyType.timeRange{}.TimeRangeType.startTime xml_time, timeInterval{}.TemporalPropertyType.dayPeriod{}.DayPropertyType.timePeriod{}.TimePropertyType.timeRange{}.TimeRangeType.endTime xml_time, publicRightOfWay xml_boolean, nationalCycleRoute xml_boolean, quietRoute xml_boolean, obstruction xml_boolean, planningOrder xml_boolean, worksProhibited xml_boolean, geometry xml_geometry
    -> DateFormatter
    -> ListExploder
    -> ListExploder_8
Note: Set output file and location
Note: Writer can be changed depending on output requirements
HighwayDedication (writer GEOPACKAGE_1)
    attributes: id text(22), identifier text(37), beginLifespanVersion datetime, validFrom datetime, reasonForChange text(32), dedication text(35), publicRightOfWay boolean, nationalCycleRoute boolean, quietRoute boolean, obstruction boolean, planningOrder boolean, worksProhibited boolean
Note: Cross references
Network_Reference (writer GEOPACKAGE_1)
    attributes: gml_id text(2048), networkRef___LinkReference_element_xlink_href text(2048)

Bookmark: Create Highways Dedication geometry
Note: Reset dates
DateFormatter
    DATE_ATTR = beginLifespanVersion
    INVALID_DATE_VALUE = _FME_NO_OP_
    SRCFMT = Unknown - Automatic Detection
    FMT = FME Date (%Y%m%d)
    -> DateFormatter_2
DateFormatter_2
    DATE_ATTR = validFrom
    INVALID_DATE_VALUE = _FME_NO_OP_
    SRCFMT = Unknown - Automatic Detection
    FMT = FME Date (%Y%m%d)
    -> StringReplacer
StringReplacer
    REGEXP = NO
    FIND_TEXT = T00:00:00.000
    REPLACE_TEXT = 000000
    SRC_ATTRS = beginLifespanVersion
    NO_MATCH = _FME_NO_OP_
    CASE = NO
    -> AttributeRenamer
Note: Rename ids
AttributeRenamer
    ATTR_TABLE:
      RENAME_SET_DEFAULT gml_id > id
      RENAME_SET_DEFAULT inspireId.Identifier.localId > identifier
    -> AttributeManager
AttributeManager
    ATTR_TABLE:
      REMOVE gml_parent_id
      REMOVE gml_parent_property
      REMOVE networkRef{}.nilReason
      REMOVE networkRef{}.xsi_nil
      REMOVE networkRef{}.NetworkReference.element.owns
      REMOVE networkRef{}.NetworkReference.element.nilReason
      REMOVE networkRef{}.NetworkReference.element.gml_remoteSchema
      REMOVE networkRef{}.NetworkReference.element.xlink_href
      REMOVE networkRef{}.LinkReference.element.owns
      REMOVE networkRef{}.LinkReference.element.nilReason
      REMOVE networkRef{}.LinkReference.element.gml_remoteSchema
      REMOVE networkRef{}.LinkReference.element.xlink_href
      REMOVE networkRef{}.LinkReference.applicableDirection.owns
      REMOVE networkRef{}.LinkReference.applicableDirection.nilReason
      REMOVE networkRef{}.LinkReference.applicableDirection.gml_remoteSchema
      REMOVE networkRef{}.LinkReference.applicableDirection.xlink_href
      REMOVE networkRef{}.LinkReference.applicableDirection.xsi_nil
      REMOVE networkRef{}.SimplePointReference.element.owns
      REMOVE networkRef{}.SimplePointReference.element.nilReason
      REMOVE networkRef{}.SimplePointReference.element.gml_remoteSchema
      REMOVE networkRef{}.SimplePointReference.element.xlink_href
      REMOVE networkRef{}.SimplePointReference.applicableDirection.owns
      REMOVE networkRef{}.SimplePointReference.applicableDirection.nilReason
      REMOVE networkRef{}.SimplePointReference.applicableDirection.gml_remoteSchema
      REMOVE networkRef{}.SimplePointReference.applicableDirection.xlink_href
      REMOVE networkRef{}.SimplePointReference.applicableDirection.xsi_nil
      REMOVE networkRef{}.SimplePointReference.atPosition
      REMOVE networkRef{}.SimplePointReference.atPosition.uom
      REMOVE networkRef{}.SimplePointReference.offset
      REMOVE networkRef{}.SimplePointReference.offset.nilReason
      REMOVE networkRef{}.SimplePointReference.offset.uom
      REMOVE networkRef{}.SimplePointReference.offset.xsi_nil
      REMOVE networkRef{}.PointReference.element.owns
      REMOVE networkRef{}.PointReference.element.nilReason
      REMOVE networkRef{}.PointReference.element.gml_remoteSchema
      REMOVE networkRef{}.PointReference.element.xlink_href
      REMOVE networkRef{}.PointReference.applicableDirection.owns
      REMOVE networkRef{}.PointReference.applicableDirection.nilReason
      REMOVE networkRef{}.PointReference.applicableDirection.gml_remoteSchema
      REMOVE networkRef{}.PointReference.applicableDirection.xlink_href
      REMOVE networkRef{}.PointReference.applicableDirection.xsi_nil
      REMOVE networkRef{}.PointReference.atPosition
      REMOVE networkRef{}.PointReference.atPosition.uom
      REMOVE networkRef{}.PointReference.offset
      REMOVE networkRef{}.PointReference.offset.nilReason
      REMOVE networkRef{}.PointReference.offset.uom
      REMOVE networkRef{}.PointReference.offset.xsi_nil
      REMOVE networkRef{}.PointReference.atPositionGeometry
      REMOVE networkRef{}.SimpleLinearReference.element.owns
      REMOVE networkRef{}.SimpleLinearReference.element.nilReason
      REMOVE networkRef{}.SimpleLinearReference.element.gml_remoteSchema
      REMOVE networkRef{}.SimpleLinearReference.element.xlink_href
      REMOVE networkRef{}.SimpleLinearReference.applicableDirection.owns
      REMOVE networkRef{}.SimpleLinearReference.applicableDirection.nilReason
      REMOVE networkRef{}.SimpleLinearReference.applicableDirection.gml_remoteSchema
      REMOVE networkRef{}.SimpleLinearReference.applicableDirection.xlink_href
      REMOVE networkRef{}.SimpleLinearReference.applicableDirection.xsi_nil
      REMOVE networkRef{}.SimpleLinearReference.fromPosition
      REMOVE networkRef{}.SimpleLinearReference.fromPosition.uom
      REMOVE networkRef{}.SimpleLinearReference.toPosition
      REMOVE networkRef{}.SimpleLinearReference.toPosition.uom
      REMOVE networkRef{}.SimpleLinearReference.offset
      REMOVE networkRef{}.SimpleLinearReference.offset.nilReason
      REMOVE networkRef{}.SimpleLinearReference.offset.uom
      REMOVE networkRef{}.SimpleLinearReference.offset.xsi_nil
      REMOVE networkRef{}.LinearReference.element.owns
      REMOVE networkRef{}.LinearReference.element.nilReason
      REMOVE networkRef{}.LinearReference.element.gml_remoteSchema
      REMOVE networkRef{}.LinearReference.element.xlink_href
      REMOVE networkRef{}.LinearReference.applicableDirection.owns
      REMOVE networkRef{}.LinearReference.applicableDirection.nilReason
      REMOVE networkRef{}.LinearReference.applicableDirection.gml_remoteSchema
      REMOVE networkRef{}.LinearReference.applicableDirection.xlink_href
      REMOVE networkRef{}.LinearReference.applicableDirection.xsi_nil
      REMOVE networkRef{}.LinearReference.fromPosition
      REMOVE networkRef{}.LinearReference.fromPosition.uom
      REMOVE networkRef{}.LinearReference.toPosition
      REMOVE networkRef{}.LinearReference.toPosition.uom
      REMOVE networkRef{}.LinearReference.offset
      REMOVE networkRef{}.LinearReference.offset.nilReason
      REMOVE networkRef{}.LinearReference.offset.uom
      REMOVE networkRef{}.LinearReference.offset.xsi_nil
      REMOVE networkRef{}.LinearReference.fromPositionGeometry
      REMOVE networkRef{}.LinearReference.toPositionGeometry
      REMOVE networkRef{}.NetworkReferenceLocation.element.owns
      REMOVE networkRef{}.NetworkReferenceLocation.element.nilReason
      REMOVE networkRef{}.NetworkReferenceLocation.element.gml_remoteSchema
      REMOVE networkRef{}.NetworkReferenceLocation.element.xlink_href
      REMOVE networkRef{}.NetworkReferenceLocation.locationDescription
      REMOVE networkRef{}.NetworkReferenceLocation.locationStart
      REMOVE networkRef{}.NetworkReferenceLocation.locationEnd
      REMOVE networkRef{}.NetworkReferenceLocation.locationLine
      REMOVE networkRef{}.NetworkReferenceLocation.locationArea
      REMOVE networkRef{}.NodeReference.element.owns
      REMOVE networkRef{}.NodeReference.element.nilReason
      REMOVE networkRef{}.NodeReference.element.gml_remoteSchema
      REMOVE networkRef{}.NodeReference.element.xlink_href
      REMOVE networkRef{}.NodeReference.location
      REMOVE networkRef{}.NodeReference.linkReference{}.nilReason
      REMOVE networkRef{}.NodeReference.linkReference{}.gml_remoteSchema
      REMOVE networkRef{}.NodeReference.linkReference{}.xlink_href
      REMOVE networkRef{}.NodeReference.linkReference{}.owns
      REMOVE inspireId.Identifier.namespace
      REMOVE inspireId.Identifier.versionId
      REMOVE inspireId.Identifier.versionId.nilReason
      REMOVE inspireId.Identifier.versionId.xsi_nil
      REMOVE beginLifespanVersion.nilReason
      REMOVE beginLifespanVersion.xsi_nil
      REMOVE endLifespanVersion
      REMOVE endLifespanVersion.nilReason
      REMOVE endLifespanVersion.xsi_nil
      REMOVE validFrom.nilReason
      REMOVE validFrom.xsi_nil
      REMOVE validTo
      REMOVE validTo.nilReason
      REMOVE validTo.xsi_nil
      REMOVE reasonForChange.codeSpace
      REMOVE dedication.codeSpace
      REMOVE timeInterval{}.TemporalPropertyType.namedDate{}
      REMOVE timeInterval{}.TemporalPropertyType.namedDate{}.codeSpace
      REMOVE timeInterval{}.TemporalPropertyType.dateRange{}.DateRangeType.startDate
      REMOVE timeInterval{}.TemporalPropertyType.dateRange{}.DateRangeType.endDate
      REMOVE timeInterval{}.TemporalPropertyType.dateRange{}.DateRangeType.startMonthDay
      REMOVE timeInterval{}.TemporalPropertyType.dateRange{}.DateRangeType.endMonthDay
      REMOVE timeInterval{}.TemporalPropertyType.dayPeriod{}.DayPropertyType.namedDay{}
      REMOVE timeInterval{}.TemporalPropertyType.dayPeriod{}.DayPropertyType.namedDay{}.codeSpace
      REMOVE timeInterval{}.TemporalPropertyType.dayPeriod{}.DayPropertyType.namedPeriod{}
      REMOVE timeInterval{}.TemporalPropertyType.dayPeriod{}.DayPropertyType.namedPeriod{}.codeSpace
      REMOVE timeInterval{}.TemporalPropertyType.dayPeriod{}.DayPropertyType.timePeriod{}.TimePropertyType.namedTime{}
      REMOVE timeInterval{}.TemporalPropertyType.dayPeriod{}.DayPropertyType.timePeriod{}.TimePropertyType.namedTime{}.codeSpace
      REMOVE timeInterval{}.TemporalPropertyType.dayPeriod{}.DayPropertyType.timePeriod{}.TimePropertyType.timeRange{}.TimeRangeType.startTime
      REMOVE timeInterval{}.TemporalPropertyType.dayPeriod{}.DayPropertyType.timePeriod{}.TimePropertyType.timeRange{}.TimeRangeType.endTime
    -> HighwayDedication (writer GEOPACKAGE_1)

Bookmark: Network_Reference
ListExploder
    ATTR_ACCUM_MODE = Merge List Attributes
    LIST_ATTR = networkRef{}
    INDEX_ATTR = _element_index
    ATTR_CONFLICT_RES = Use List Attribute Values
    ELEMENTS -> AttributeKeeper
AttributeKeeper
    KEEP_ATTRS = NetworkReference.element.xlink_href,gml_id
    -> AttributeTrimmer
Note: Remove # to enable table joins
AttributeTrimmer
    TRIM_CHARS = #
    TRIM_TO_NONE = Yes
    SRC_ATTRS = NetworkReference.element.xlink_href
    TRIM_TYPE = Left
    -> Network_Reference (writer GEOPACKAGE_1)

Bookmark: Time qualifiers
ListExploder_8
    ATTR_ACCUM_MODE = Merge Incoming List
    LIST_ATTR = timeInterval{}
    INDEX_ATTR = _element_index
    ATTR_CONFLICT_RES = Use Original
    LIST_FOUND -> AttributeRenamer_17
AttributeRenamer_17
    ATTR_TABLE = RENAME_SET_DEFAULT gml_id > parentFeature_ID
    -> Counter
Note: Creates an identifier for date element
Counter
    DOMAIN = counter
    START = 0
    SCOPE = Global
    CNT_ATTR = timeInterval_ID
    -> ListExploder_9
    -> TQ_Parent_Date_Join (writer GEOPACKAGE_1)
    -> ListExploder_10
    -> ListExploder_11
ListExploder_11
    ATTR_ACCUM_MODE = Merge Incoming List
    LIST_ATTR = TemporalPropertyType.dayPeriod{}
    INDEX_ATTR = _element_index
    ATTR_CONFLICT_RES = Use Original
    LIST_FOUND -> Counter_2
Note: Creates an identifier for day element
Counter_2
    DOMAIN = counter
    START = 0
    SCOPE = Global
    CNT_ATTR = dayPeriod_ID
    -> ListExploder_12
    -> ListExploder_13
    -> ListExploder_14
    -> TQ_Date_Day_Join (writer GEOPACKAGE_1)
Note: Some transformers are incomplete as the data is not currently present
ListExploder_14
    ATTR_ACCUM_MODE = Merge Incoming List
    LIST_ATTR = DayPropertyType.timePeriod{}
    INDEX_ATTR = _element_index
    ATTR_CONFLICT_RES = Use Original
    LIST_FOUND -> Counter_3
Note: Creates an identifier for time element
Counter_3
    DOMAIN = counter
    START = 0
    SCOPE = Global
    CNT_ATTR = timePeriod_ID
    -> ListExploder_15
    -> ListExploder_16
    -> TQ_Day_Time_Join (writer GEOPACKAGE_1)

Bookmark: Date element
TQ_Parent_Date_Join (writer GEOPACKAGE_1)
    attributes: parentFeature_ID text(50), timeInterval_ID mediumint

Bookmark: DateRange
ListExploder_9
    ATTR_ACCUM_MODE = Merge Incoming List
    LIST_ATTR = TemporalPropertyType.dateRange{}
    INDEX_ATTR = _element_index
    ATTR_CONFLICT_RES = Use Original
    LIST_FOUND -> AttributeRenamer_6
AttributeRenamer_6
    ATTR_LIST = DateRangeType.startDate,startDate,,DateRangeType.endDate,endDate,,DateRangeType.startMonthDay,startMonthDay,,DateRangeType.endMonthDay,endMonthDay,
    -> DateFormatter_3
DateFormatter_3
    DATE_ATTR = endDate,startDate
    INVALID_DATE_VALUE = _FME_NO_OP_
    SRCFMT = Unknown - Automatic Detection
    FMT = FME Date (%Y%m%d)
    -> TQ_DateRange (writer GEOPACKAGE_1)
TQ_DateRange (writer GEOPACKAGE_1)
    attributes: parentFeature_ID text(50), timeInterval_ID mediumint, startDate datetime, endDate datetime, startMonthDay text(10), endMonthDay text(10)

Bookmark: NamedDate
ListExploder_10
    ATTR_ACCUM_MODE = Merge Incoming List
    LIST_ATTR = TemporalPropertyType.namedDate{}
    INDEX_ATTR = _element_index
    ATTR_CONFLICT_RES = Use Original
    LIST_FOUND -> AttributeRenamer_12
AttributeRenamer_12
    ATTR_LIST = TemporalPropertyType.namedDate,namedDate,
    -> TQ_NamedDate (writer GEOPACKAGE_1)
TQ_NamedDate (writer GEOPACKAGE_1)
    attributes: parentFeature_ID text(50), timeInterval_ID mediumint, namedDate text(20)

Bookmark: Day element
TQ_Date_Day_Join (writer GEOPACKAGE_1)
    attributes: parentFeature_ID text(50), timeInterval_ID mediumint, dayPeriod_ID mediumint

Bookmark: NamedDay
ListExploder_12
    ATTR_ACCUM_MODE = Merge Incoming List
    LIST_ATTR = DayPropertyType.namedDay{}
    INDEX_ATTR = _element_index
    ATTR_CONFLICT_RES = Use Original
    LIST_FOUND -> AttributeRenamer_13
AttributeRenamer_13
    ATTR_LIST = DayPropertyType.namedDay,namedDay,
    -> TQ_NamedDay (writer GEOPACKAGE_1)
TQ_NamedDay (writer GEOPACKAGE_1)
    attributes: parentFeature_ID text(50), timeInterval_ID mediumint, dayPeriod_ID mediumint, namedDay text(50)

Bookmark: NamedPeriod
ListExploder_13
    ATTR_ACCUM_MODE = Merge Incoming List
    LIST_ATTR = DayPropertyType.namedPeriod{}
    INDEX_ATTR = _element_index
    ATTR_CONFLICT_RES = Use Original
    LIST_FOUND -> AttributeRenamer_14
AttributeRenamer_14
    ATTR_LIST = DayPropertyType.namedPeriod,namedPeriod,
    -> TQ_NamedPeriod (writer GEOPACKAGE_1)
TQ_NamedPeriod (writer GEOPACKAGE_1)
    attributes: parentFeature_ID text(50), timeInterval_ID mediumint, dayPeriod_ID mediumint, namedPeriod text(50)

Bookmark: Time element
TQ_Day_Time_Join (writer GEOPACKAGE_1)
    attributes: parentFeature_ID text(50), timeInterval_ID mediumint, dayPeriod_ID mediumint, timePeriod_ID mediumint

Bookmark: TimeRange
ListExploder_15
    ATTR_ACCUM_MODE = Merge Incoming List
    LIST_ATTR = TimePropertyType.timeRange{}
    INDEX_ATTR = _element_index
    ATTR_CONFLICT_RES = Use Original
    LIST_FOUND -> AttributeRenamer_15
AttributeRenamer_15
    ATTR_LIST = TimeRangeType.startTime,startTime,,TimeRangeType.endTime,endTime,
    -> TQ_TimeRange (writer GEOPACKAGE_1)
TQ_TimeRange (writer GEOPACKAGE_1)
    attributes: parentFeature_ID text(50), timeInterval_ID mediumint, dayPeriod_ID mediumint, timePeriod_ID mediumint, startTime text(10), endTime text(10)

Bookmark: NamedTime
ListExploder_16
    ATTR_ACCUM_MODE = Merge Incoming List
    LIST_ATTR = TimePropertyType.namedTime{}
    INDEX_ATTR = _element_index
    ATTR_CONFLICT_RES = Use Original
    LIST_FOUND -> AttributeRenamer_16
AttributeRenamer_16
    ATTR_LIST = TimePropertyType.namedTime,namedTime,
    -> TQ_NamedTime (writer GEOPACKAGE_1)
TQ_NamedTime (writer GEOPACKAGE_1)
    attributes: parentFeature_ID text(50), timeInterval_ID mediumint, dayPeriod_ID mediumint, timePeriod_ID mediumint, namedTime text(50)
