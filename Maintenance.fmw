FME workspace Maintenance.fmw

Parameters:
- SourceDataset_GML_3 = W:\cdp_prod\1_Bulpitt_E\WIP\newHighwaysWorkbenches\newSpecSampleData\HighwaysSampleData_1708\FULL\Highways_Rrami_Maintenance_FULL_001.gml   # Source Geography Markup Language (GML) File(s)
- DestDataset_GEOPACKAGE =   # GeoPackage File

Readers:
- GML_1: GML from $(SourceDataset_GML_3) in EPSG:27700

Writers:
- GEOPACKAGE_1: GEOPACKAGE to $(DestDataset_GEOPACKAGE)

Note: Change output to prefered format
Note: All Maintenance features will reference back to the Street feature (the USRN) of the Linear Highway Network. A single Maintenance feature will not reference multiple Street features. The Maintenance feature has come directly from the NSG. / Maintenance features may reference a whole Street feature and in this instance no geometry is provided. / A Maintenance feature may only partially reference the Street feature. In these instances a location description is provided and a start location and end location will be provided where they are within 10m of the network. When geometry is provided both a start location and an end location will be provided which results in the feature having a mult point geometry.
Maintenance (reader GML_1)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean, networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer,
      networkRef{}.LinkReference.applicableDirection.xsi_nil xml_boolean, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean, networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean, networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer,
      networkRef{}.PointReference.offset.xsi_nil xml_boolean, networkRef{}.PointReference.atPositionGeometry xml_geometry, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer, networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer,
      networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, maintenanceResponsibility xml_char(44), maintenanceAuthority.ResponsibleAuthority.identifier xml_buffer, maintenanceAuthority.ResponsibleAuthority.authorityName xml_buffer, partialReference xml_boolean, highwayAuthority.ResponsibleAuthority.identifier xml_buffer,
      highwayAuthority.ResponsibleAuthority.authorityName xml_buffer, reasonForChange xml_buffer, reasonForChange.codeSpace xml_buffer
    -> ListIndexer

Bookmark: Create Maintenance feature. The network reference is included in this feature output.
Note: Pull out the first network reference, / there will only ever be one.
ListIndexer
    INDEX = 0
    LIST_ATTR = networkRef{}
    PREFIX = net_ref_
    -> AttributeRenamer_3
AttributeRenamer_3
    ATTR_LIST = inspireId.Identifier.localId,localId,,highwayAuthority.ResponsibleAuthority.authorityName,highwayAuthorityName,,maintenanceAuthority.ResponsibleAuthority.authorityName,maintenanceAuthorityName,,maintenanceAuthority.ResponsibleAuthority.identifier,maintenanceAuthorityID,,highwayAuthority.ResponsibleAuthority.identifier,highwayAuthorityID,,inspireId.Identifier.versionId,versionID,,gml_id,ID,,networkRef{0}.NetworkReference.element.xlink_href,referenceToStreetUSRN,
    -> DateFormatter
DateFormatter
    DATE_ATTR = beginLifespanVersion,endLifespanVersion,validFrom,validTo
    INVALID_DATE_VALUE = FME_NULL_VALUE
    SRCFMT = %Y"-"%m"-"%d"T"%T
    FMT = FME Date (%Y%m%d)
    -> TestFilter
Note: Identify if the Maintenance feature partially references the Network. If the result is "True" then the network reference is held in a different attribute and splitting here will enable bringing the Network reference into the same attribute in the final result.
TestFilter
    TEST_LIST = BOOL_OP,OR,COMPOSITE_TEST,<Unused>,TEST_CLAUSE,"TEST @Value(partialReference) = false",False,BOOL_OP,OR,COMPOSITE_TEST,<Unused>,TEST_CLAUSE,"TEST @Value(partialReference) = true",True
    DEFAULT_VALUE = <UNFILTERED>
    False -> AttributeRenamer_2
    True -> AttributeRenamer
AttributeRenamer_2
    ATTR_LIST = net_ref_NetworkReference.element.xlink_href,referencetostreetusrn,,net_ref_NetworkReferenceLocation.locationDescription,locationdescription,
    -> StringReplacer
AttributeRenamer
    ATTR_LIST = net_ref_NetworkReferenceLocation.element.xlink_href,referenceToStreetUSRN,,net_ref_NetworkReferenceLocation.locationDescription,locationDescription,
    -> StringReplacer
Note: remove # from the / feature references
StringReplacer
    FIND_TEXT = #
    CASE = no
    NO_MATCH = _FME_NO_OP_
    SRC_ATTRS = referenceToStreetUSRN
    REGEXP = no
    -> GeometryFilter
GeometryFilter
    GEOM_PORT_NAMES = Point Line Area
    BREAK_AGG = No
    POINT -> Maintenance_point (writer GEOPACKAGE_1)
    LINE -> Maintenance_line (writer GEOPACKAGE_1)
    AREA -> Maintenance_area (writer GEOPACKAGE_1)
    <UNFILTERED> -> Maintenance_noGeom (writer GEOPACKAGE_1)
Maintenance_point (writer GEOPACKAGE_1)
    attributes: ID text(20), localId text(37), beginLifespanVersion datetime, validFrom datetime, maintenanceResponsibility text(120), partialReference text(20), highwayAuthorityName text(120), highwayAuthorityID mediumint, maintenanceAuthorityName text(120), maintenanceAuthorityID mediumint, referenceToStreetUSRN text(20), reasonForChange text(32), locationDescription text(120)
Maintenance_line (writer GEOPACKAGE_1)
    attributes: ID text(20), localId text(37), beginLifespanVersion datetime, validFrom datetime, maintenanceResponsibility text(120), partialReference text(20), highwayAuthorityName text(120), highwayAuthorityID mediumint, maintenanceAuthorityName text(120), maintenanceAuthorityID mediumint, referenceToStreetUSRN text(20), reasonForChange text(32), locationDescription text(120)
Maintenance_area (writer GEOPACKAGE_1)
    attributes: ID text(20), localId text(37), beginLifespanVersion datetime, validFrom datetime, maintenanceResponsibility text(120), partialReference text(20), highwayAuthorityName text(120), highwayAuthorityID mediumint, maintenanceAuthorityName text(120), maintenanceAuthorityID mediumint, referenceToStreetUSRN text(20), reasonForChange text(32), locationDescription text(120)
Note: This is an example output, writer will need to be added for specific output
Maintenance_noGeom (writer GEOPACKAGE_1)
    attributes: ID text(20), localId text(37), beginLifespanVersion datetime, validFrom datetime, maintenanceResponsibility text(120), partialReference text(20), highwayAuthorityName text(120), highwayAuthorityID mediumint, maintenanceAuthorityName text(120), maintenanceAuthorityID mediumint, referenceToStreetUSRN text(20), reasonForChange text(32), locationDescription text(120)
