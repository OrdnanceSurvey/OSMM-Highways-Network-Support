FME workspace RoadNode.fmw

Parameters:
- SourceDataset_GML = C:\Temp\Highways_Data\Highways_RoadsAndRAM_RoadNode_001.gml.gz   # Source Geography Markup Language (GML) File(s)
- DestDataset_GEOPACKAGE =   # Destination GeoPackage File

Readers:
- GML_1: GML from $(SourceDataset_GML)

Writers:
- GEOPACKAGE_1: GEOPACKAGE to $(DestDataset_GEOPACKAGE)

Note: Change to local input
RoadNode (reader GML_1)
    attributes: beginLifespanVersion xml_char(24), classification xml_char(18), classification.codeSpace xml_char(72), formOfRoadNode.owns xml_char(6), formOfRoadNode.xlink_href xml_char(77), inNetwork{}.owns xml_char(6), inNetwork{}.xlink_href xml_char(18), inspireId.Identifier.localId xml_decimal(17,0), inspireId.Identifier.namespace xml_char(19), junctionNumber{} xml_char(21), reasonForChange xml_char(4), reasonForChange.codeSpace xml_char(47), relatedRoadArea{}.owns xml_char(6), relatedRoadArea{}.xlink_href xml_char(22), validFrom xml_char(1), validFrom.nilReason xml_char(8), validFrom.xsi_nil xml_char(5)
    -> AttributeRenamer_2
Note: Rename attributes
Note: This is an example output, writer will need to be added for specific output
AttributeRenamer_2
    ATTR_LIST = gml_id,TOID,,inspireId.Identifier.localId,identifier,
    -> DateFormatter
    -> ListExploder_3

Bookmark: Create RoadNode feature
Note: reformat as DMY
DateFormatter
    DATE_ATTR = beginLifespanVersion,validFrom
    SRCFMT = Unknown - Automatic Detection
    INVALID_DATE_VALUE = _FME_NO_OP_
    FMT = FME Date (%Y%m%d)
    -> AttributeRenamer
AttributeRenamer
    ATTR_LIST = inspireId.Identifier.namespace,identifierNamespace,,inspireId.Identifier.versionId,identifierVersionId,,inspireId.Identifier.localId,localId,,junctionNumber{0},junctionNumber1,,relatedRoadArea{0}.xlink_href,relatedRoadArea,,junctionNumber{1},junctionNumber2,
    -> AttributeSplitter
Note: The attribute value for "formOfRoadNode" is held as a / URL therefore to extract the value from the URL / the attribute needs splitting after every "/". This / action will create a list. The values after the last / "/" will contain the attribute value.
AttributeSplitter
    TRIM_OPTION = Both
    ATTR_NAME = formOfRoadNode.xlink_href
    LIST_NAME = form_list
    DROP_EMPTY_PARTS = No
    DELIMITER = /
    -> AttributeRenamer_4
Note: Renaming the last list produced by the / AttributeSplitter which holds the attribute / value for the "directionality" attribute.
AttributeRenamer_4
    ATTR_LIST = form_list{5},formofRoadNode,
    -> RoadNode (writer GEOPACKAGE_1)
RoadNode (writer GEOPACKAGE_1)
    attributes: TOID text(20), identifier text(37), beginLifespanVersion datetime, validFrom datetime, formOfRoadNode text(21), classification text(19), access text(5), junctionNumber1 text(30), junctionNumber2 text(30), junctionName1_text text(120), junctionName1_lang text(3), junctionName2_text text(120), junctionName2_lang text(3), reasonForChange text(32)

Bookmark: The OS MasterMap Topography Layer TOID reference that the RoadNode sits within
ListExploder_3
    ATTR_CONFLICT_RES = Use Original
    INDEX_ATTR = _element_index
    ATTR_ACCUM_MODE = Merge Incoming List
    LIST_ATTR = relatedRoadArea{}
    LIST_FOUND -> AttributeRenamer_10
AttributeRenamer_10
    ATTR_LIST = xlink_href,RelatedRoadAreaTOID,
    -> StringReplacer
Note: remove # from the / feature references
StringReplacer
    NO_MATCH = _FME_NO_OP_
    SRC_ATTRS = RelatedRoadAreaTOID
    REGEXP = no
    FIND_TEXT = #
    CASE = no
    -> RoadNode_RelatedRoadArea (writer GEOPACKAGE_1)
RoadNode_RelatedRoadArea (writer GEOPACKAGE_1)
    attributes: TOID text(20), relatedRoadAreaToid text(20)
