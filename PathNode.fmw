FME workspace PathNode.fmw

Parameters:
- SourceDataset_GML = C:\Temp\Highways_Data\Paths\Bedford_PathNode.gml.gz   # Source Geography Markup Language (GML) File(s)
- DestDataset_GEOPACKAGE =   # Destination GeoPackage File

Readers:
- GML_1: GML from $(SourceDataset_GML)

Writers:
- GEOPACKAGE_1: GEOPACKAGE to $(DestDataset_GEOPACKAGE)

Note: Change input to local GML
PathNode (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, geometry xml_geometry, spokeEnd{}.owns xml_boolean, spokeEnd{}.nilReason xml_buffer, spokeEnd{}.gml_remoteSchema xml_buffer, spokeEnd{}.xlink_href xml_buffer, spokeEnd{}.xsi_nil xml_boolean, spokeStart{}.owns xml_boolean, spokeStart{}.nilReason xml_buffer, spokeStart{}.gml_remoteSchema xml_buffer, spokeStart{}.xlink_href xml_buffer, spokeStart{}.xsi_nil xml_boolean, geographicalName.nilReason xml_buffer, geographicalName.xsi_nil xml_boolean, geographicalName.GeographicalName.language xml_buffer,
      geographicalName.GeographicalName.language.nilReason xml_buffer, geographicalName.GeographicalName.language.xsi_nil xml_boolean, geographicalName.GeographicalName.nativeness.owns xml_boolean, geographicalName.GeographicalName.nativeness.nilReason xml_buffer, geographicalName.GeographicalName.nativeness.gml_remoteSchema xml_buffer, geographicalName.GeographicalName.nativeness.xlink_href xml_buffer, geographicalName.GeographicalName.nativeness.xsi_nil xml_boolean, geographicalName.GeographicalName.nameStatus.owns xml_boolean, geographicalName.GeographicalName.nameStatus.nilReason xml_buffer, geographicalName.GeographicalName.nameStatus.gml_remoteSchema xml_buffer, geographicalName.GeographicalName.nameStatus.xlink_href xml_buffer, geographicalName.GeographicalName.nameStatus.xsi_nil xml_boolean, geographicalName.GeographicalName.sourceOfName xml_buffer, geographicalName.GeographicalName.sourceOfName.nilReason xml_buffer, geographicalName.GeographicalName.sourceOfName.xsi_nil xml_boolean, geographicalName.GeographicalName.pronunciation.nilReason xml_buffer, geographicalName.GeographicalName.pronunciation.xsi_nil xml_boolean, geographicalName.GeographicalName.pronunciation.PronunciationOfName.pronunciationSoundLink xml_buffer, geographicalName.GeographicalName.pronunciation.PronunciationOfName.pronunciationSoundLink.nilReason xml_buffer, geographicalName.GeographicalName.pronunciation.PronunciationOfName.pronunciationSoundLink.xsi_nil xml_boolean, geographicalName.GeographicalName.pronunciation.PronunciationOfName.pronunciationIPA xml_buffer, geographicalName.GeographicalName.pronunciation.PronunciationOfName.pronunciationIPA.nilReason xml_buffer, geographicalName.GeographicalName.pronunciation.PronunciationOfName.pronunciationIPA.xsi_nil xml_boolean, geographicalName.GeographicalName.spelling{}.SpellingOfName.text xml_buffer, geographicalName.GeographicalName.spelling{}.SpellingOfName.script xml_buffer, geographicalName.GeographicalName.spelling{}.SpellingOfName.script.nilReason xml_buffer, geographicalName.GeographicalName.spelling{}.SpellingOfName.script.xsi_nil xml_boolean, geographicalName.GeographicalName.spelling{}.SpellingOfName.transliterationScheme xml_buffer, geographicalName.GeographicalName.spelling{}.SpellingOfName.transliterationScheme.nilReason xml_buffer, geographicalName.GeographicalName.spelling{}.SpellingOfName.transliterationScheme.xsi_nil xml_boolean,
      geographicalName.GeographicalName.grammaticalGender.owns xml_boolean, geographicalName.GeographicalName.grammaticalGender.nilReason xml_buffer, geographicalName.GeographicalName.grammaticalGender.gml_remoteSchema xml_buffer, geographicalName.GeographicalName.grammaticalGender.xlink_href xml_buffer, geographicalName.GeographicalName.grammaticalGender.xsi_nil xml_boolean, geographicalName.GeographicalName.grammaticalNumber.owns xml_boolean, geographicalName.GeographicalName.grammaticalNumber.nilReason xml_buffer, geographicalName.GeographicalName.grammaticalNumber.gml_remoteSchema xml_buffer, geographicalName.GeographicalName.grammaticalNumber.xlink_href xml_buffer, geographicalName.GeographicalName.grammaticalNumber.xsi_nil xml_boolean, validFrom xml_datetime, validFrom.nilReason xml_buffer, validFrom.xsi_nil xml_boolean, validTo xml_datetime, validTo.nilReason xml_buffer, validTo.xsi_nil xml_boolean, formOfRoadNode.owns xml_boolean, formOfRoadNode.nilReason xml_buffer, formOfRoadNode.gml_remoteSchema xml_buffer, formOfRoadNode.xlink_href xml_buffer, formOfRoadNode.xsi_nil xml_boolean, reasonForChange xml_buffer, reasonForChange.codeSpace xml_buffer, classification xml_buffer, classification.codeSpace xml_buffer
    -> AttributeRenamer_2
Note: Rename attributes
AttributeRenamer_2
    ATTR_LIST = gml_id,TOID,,inspireId.Identifier.localId,localId,
    -> DateFormatter
Note: Change output to prefered format
PathNode (writer GEOPACKAGE_1)
    attributes: TOID text(20), localId text(37), beginLifespanVersion datetime, validFrom datetime, formofRoadNode text(21), reasonForChange text(32), classification text(19)

Bookmark: Create PathNode
Note: reformat as DMY
DateFormatter
    DATE_ATTR = beginLifespanVersion,validFrom
    SRCFMT = Unknown - Automatic Detection
    INVALID_DATE_VALUE = _FME_NO_OP_
    FMT = FME Date (%Y%m%d)
    -> AttributeRenamer
AttributeRenamer
    ATTR_LIST = inspireId.Identifier.namespace,identifierNamespace,,inspireId.Identifier.versionId,identifierVersionId,,inspireId.Identifier.localId,localId,
    -> AttributeSplitter
Note: The attribute value for "formOfRoadNode" is held as a / URL therefore to extract the value from the URL / the attribute needs splitting after every "/". This / action will create a list. The values after the last / "/" will contain the attribute value.
AttributeSplitter
    ATTR_NAME = formOfRoadNode.xlink_href
    LIST_NAME = form_list
    TRIM_OPTION = Both
    DELIMITER = /
    DROP_EMPTY_PARTS = No
    -> AttributeRenamer_4
Note: Rename formOfRoadNode
AttributeRenamer_4
    ATTR_LIST = form_list{5},formofRoadNode,
    -> PathNode (writer GEOPACKAGE_1)
